from __future__ import division # allows floating point division from integers
import FreeCAD, Part, math
import datetime
import random
from FreeCAD import Base
from lento import lento
from inrun2 import inrun
from inrun2 import takeoff2
from scipy import *

class LahtiTest2:
    def __init__(self, obj):
        ''' Add the properties: Korkeus, Leveys, Pituus, Segments (see Property View) '''
        obj.addProperty("App::PropertyLength","Korkeus","Laatikko","Laatikon korkeus").Korkeus=20.0
        obj.addProperty("App::PropertyLength","Leveys","Laatikko","Laatikon leveys").Leveys=30.0
        obj.addProperty("App::PropertyLength","Pituus","Laatikko","Length of the block").Pituus=18.0
        obj.addProperty("App::PropertyLength","Segments","Laatikko","Number of the line segments").Segments=72
        obj.addProperty("App::PropertyLength","AlasKulma","Laatikko","Alastulon kulma").AlasKulma=30.0
        obj.addProperty("App::PropertyLength","AlasKorkeus","Laatikko","Alastulon korkeus").AlasKorkeus=17.0
        obj.addProperty("App::PropertyLength","InrunHeight","Laatikko","Inrun korkeus").InrunHeight=27.0
        obj.addProperty("App::PropertyLength","RunAngle","Laatikko","Vauhdinoton kulma").RunAngle=31.0
        obj.addProperty("App::PropertyLength","Radius","Laatikko","Transition sade").Radius=20.0
        obj.addProperty("App::PropertyLength","Flat","Laatikko","Flatin pituus").Flat=5.0
        obj.addProperty("App::PropertyLength","TakeoffAngle","Laatikko","Takeoff angle").TakeoffAngle=35.0
        obj.addProperty("App::PropertyLength","TakeoffHeight","Laatikko","Takeoff height").TakeoffHeight=4.0
        obj.Proxy = self

    def onChanged(self, fp, prop):
        if prop == "Korkeus" or prop == "Leveys" or prop == "Pituus" or prop == "Segments" or prop=="AlasKorkeus" or prop == "AlasKulma" or prop == "InrunHeight" or prop == "RunAngle" or prop == "Radius" or prop== "Flat" or prop == "TakeoffAngle" or prop == "TakeoffHeight" : #if one of these is changed
            self.execute(fp)

    def execute(self, fp): #main part of script
        steps=int(fp.Segments) #get value from property
        
        kor=fp.Korkeus
        lev=fp.Leveys
        pit=fp.Pituus
        alaskul = fp.AlasKulma
        alaskor = fp.AlasKorkeus          
	runangle = fp.RunAngle
	radius = fp.Radius
	ylengthstr = fp.InrunHeight - (radius - cos(runangle)*radius) #this is height of the straight section of inrun
	flat = fp.Flat
        kul=fp.TakeoffAngle
	takekork=fp.TakeoffHeight - (radius-cos(kul*2.*pi/360.)*radius) #this is the total height of the takeoff, not correct if desired angle of takeoff is not reached at this point
       
	inruninfo = inrun(runangle*2.*pi/360.,0,0,0,ylengthstr,runangle*2.*pi/360.,radius,flat,kul*2.*pi/360.,takekork)				#inrun path
	[kode,sxloppu,syloppu,vxloppu,vyloppu] = takeoff2(ylengthstr,runangle*2.*pi/360.,radius,flat,kul*2.*pi/360.,takekork) #checkin the takeoff point
	#print kode
	#print vyloppu

        edge1 = Part.makeLine((sxloppu,0,syloppu), (sxloppu+pit,0,syloppu+alaskor-kor)) #lines needed to create rectangle
        edge2 = Part.makeLine((sxloppu,0,syloppu-kor),(sxloppu,0,syloppu))
        edge3 = Part.makeLine((sxloppu+pit,0,syloppu-kor), (sxloppu+pit,0,syloppu+alaskor-kor))
        edge4 = Part.makeLine((sxloppu,0,syloppu-kor), (sxloppu+pit,0,syloppu-kor))
        takeof = Part.makeLine((-kor/tan(kul*2*pi/360)+sxloppu,0,syloppu-kor),(sxloppu,0,syloppu))
        takeofpohja = Part.makeLine((-kor/tan(kul*2*pi/360)+sxloppu,0,syloppu-kor),(sxloppu,0,syloppu-kor))
        takeofpysty = Part.makeLine((sxloppu,0,syloppu-kor),(sxloppu,0,syloppu))
        land = Part.makeLine((sxloppu+pit,0,syloppu+alaskor-kor),(sxloppu+pit+alaskor/tan(alaskul*pi*2/360),0,syloppu-kor))
        landpohja = Part.makeLine((sxloppu+pit,0,syloppu-kor),(sxloppu+pit+alaskor/tan(alaskul*pi*2/360),0,syloppu-kor))
#
#
        lentorata = lento(sxloppu,syloppu,vxloppu,vyloppu) #calculating the flightpath by script lento.py
        landwire=Part.Wire([edge3,land,landpohja])
        faceland=Part.Face(landwire)
        extland=faceland.extrude(Base.Vector(0,lev,0)) #extrude landing


        #make for loop to catch the steps of the inruninfo
        for i in range(len(inruninfo[1][:kode])-1):
        	if i==0:
			j=i
        		segInrun=Part.makeLine((inruninfo[1][j,0],0,inruninfo[2][j,0]),(inruninfo[1][j+1,0],0,inruninfo[2][j+1,0]))
        		wireInrun=Part.Wire([segInrun])
			#print "eka indeksi"
        		
        	elif i==j+20:
	
        		segInrun=Part.makeLine((inruninfo[1][j,0],0,inruninfo[2][j,0]),(inruninfo[1][i,0],0,inruninfo[2][i,0]))
			j=i
        		wireInrun=Part.Wire([wireInrun,segInrun])
        		veInrun=wireInrun.Vertexes[1]
		elif i!=(len(inruninfo[1][:kode])-1) and i>(len(inruninfo[1][:kode])-1)-10:
			k=(len(inruninfo[1][:kode])-1)
        		segInrun=Part.makeLine((inruninfo[1][j,0],0,inruninfo[2][j,0]),(inruninfo[1][k,0],0,inruninfo[2][k,0]))
        		wireInrun=Part.Wire([wireInrun,segInrun])
        		veInrun=wireInrun.Vertexes[1]

        extInrun = wireInrun.extrude(Base.Vector(0,lev/2,0)) #extrude inruninfo
        #make for loop to catch the steps of the flightpath
        for i in range(len(lentorata[1])-1):
        	if i==0:
        		seg=Part.makeLine((lentorata[1][i,0],0,lentorata[2][i,0]),(lentorata[1][i+1,0],0,lentorata[2][i+1,0]))
        		wire2=Part.Wire([seg])
        		
        	else:
        		seg=Part.makeLine((lentorata[1][i,0],0,lentorata[2][i,0]),(lentorata[1][i+1,0],0,lentorata[2][i+1,0]))
        		wire2=Part.Wire([wire2,seg])
        		ve=wire2.Vertexes[1]
        #next thing when hit landing
        #while path_x == land_x and path_y < land_y
        #try:
        #	ve=wire2.Vertexes[i]
        #	extland.isInside(Base.Vector(ve.X,ve.Y,ve.Z)

        #edgerandom = Part.makeLine((0,0,kor), (,lev,kor))
        #roska=Part.Wire([edgerandom])
        takeofwire =Part.Wire([takeof,takeofpohja,takeofpysty])

        wire1 = Part.Wire([edge1,edge2,edge3,edge4]) #rectangle
        face1 = Part.Face(wire1) #face from rectangle
        facetakeof = Part.Face(takeofwire)
        ext=face1.extrude(Base.Vector(0,lev,0)) #extrude the (face)
        exttake = facetakeof.extrude(Base.Vector(0,lev,0)) #extrude takeof
        extflight = wire2.extrude(Base.Vector(0,lev/2,0)) #extrude flightpath

        final=Part.Compound([extInrun,extflight,ext,exttake,extland])
        fp.Shape = final #ext #result shape

def makeLahtiTest2():
    doc = FreeCAD.activeDocument()
    pic = App.activeDocument()
    if pic == None:
	pic = App.newDocument()
    if doc == None:
        doc = FreeCAD.newDocument()
    lahtiTest2=doc.addObject("Part::FeaturePython","Urpo") #add object to document
    lahtiTest2.Label = "Urponkuva"
    LahtiTest2(lahtiTest2)
    lahtiTest2.ViewObject.Proxy=0
    App.activeDocument().addObject('Drawing::FeaturePage','Page')
    App.activeDocument().Page.Template = App.getResourceDir()+'Mod/Drawing/Templates/A3_Landscape.svg'    
#    App.activeDocument().Page.EditableTexts[0]='Joku muu'
    App.activeDocument().Page.EditableTexts = ['Lefthanded inc.','23 ad.','Apes',str(datetime.date.today()),'1:1000','320kg','1','112','Jump','2012/13']
#Editables in order of appearance:
#Me and my gay friends
#1990 ekr
#Tuomo the Superwisor
#Deadline yesterday
#1:1000
#WEIGHT
#NUMBER
#SHEET
#SOTS
#Lahti 2013


    App.activeDocument().addObject('Drawing::FeatureViewPart','View')
    App.activeDocument().View.Source = App.activeDocument().Urpo
    App.activeDocument().View.Direction = (0.0,0.0,1.0)
    App.activeDocument().View.X = 10.0
    App.activeDocument().View.Y = 10.0
    App.activeDocument().Page.addObject(App.activeDocument().View)
    App.activeDocument().View.X = 30.0
    App.activeDocument().View.Y = 30.0
    App.activeDocument().View.Scale = 1.5

    App.activeDocument().addObject('Drawing::FeatureViewPart','ViewRot')
    App.activeDocument().ViewRot.Source = App.activeDocument().Urpo
    App.activeDocument().ViewRot.Direction = (0.0,-1.0,0.0)
    App.activeDocument().ViewRot.X = 240.0
    App.activeDocument().ViewRot.Y = 180.0
    App.activeDocument().ViewRot.Scale = 1.8
    App.activeDocument().ViewRot.Rotation = 90.0
    App.activeDocument().Page.addObject(App.activeDocument().ViewRot) 

    App.activeDocument().addObject('Drawing::FeatureViewPart','ViewIso')
    App.activeDocument().ViewIso.Source = App.activeDocument().Urpo
    App.activeDocument().ViewIso.Direction = (0.5,1.0,1.0)
    App.activeDocument().ViewIso.X = 285.0
    App.activeDocument().ViewIso.Y = 190.0
    App.activeDocument().ViewIso.Scale = 1.4
    App.activeDocument().ViewIso.ShowHiddenLines = True
    App.activeDocument().Page.addObject(App.activeDocument().ViewIso) 

    App.activeDocument().recompute()

    print "Resulting SVG document: ",App.activeDocument().Page.PageResult
    file = open(App.activeDocument().Page.PageResult,"r")
    print "Result page is ",len(file.readlines())," lines long"
if __name__ == "__main__": #feature will be generated after macro execution
    makeLahtiTest2()
