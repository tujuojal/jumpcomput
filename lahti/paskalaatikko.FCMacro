from __future__ import division # allows floating point division from integers
import FreeCAD, Part, math
from FreeCAD import Base
from lento import lento
from scipy import *

class PaskaLaatikko:
    def __init__(self, obj):
        ''' Add the properties: Korkeus, Leveys, Pituus, Segments (see Property View) '''
        obj.addProperty("App::PropertyLength","Korkeus","Laatikko","Laatikon korkeus").Korkeus=20.0
        obj.addProperty("App::PropertyLength","Leveys","Laatikko","Laatikon leveys").Leveys=30.0
        obj.addProperty("App::PropertyLength","Pituus","Laatikko","Length of the block").Pituus=20.0
        obj.addProperty("App::PropertyLength","Segments","Laatikko","Number of the line segments").Segments=72
        obj.addProperty("App::PropertyLength","Kulma","Laatikko","Nokan kulma").Kulma=30.0
        obj.addProperty("App::PropertyLength","AlasKulma","Laatikko","Alastulon kulma").AlasKulma=30.0
        obj.addProperty("App::PropertyLength","AlasKorkeus","Laatikko","Alastulon korkeus").AlasKorkeus=20.0
        obj.addProperty("App::PropertyLength","Nopeus","Laatikko","Nopeus nokalla km/h").Nopeus=40.0
        obj.Proxy = self

    def onChanged(self, fp, prop):
        if prop == "Nopeus" or prop == "Korkeus" or prop == "Kulma" or prop == "Leveys" or prop == "Pituus" or prop == "Segments" or prop=="AlasKorkeus" or prop == "AlasKulma": #if one of these is changed
            self.execute(fp)

    def execute(self, fp): #main part of script
        steps=int(fp.Segments) #get value from property
        
        nop=fp.Nopeus
        kor=fp.Korkeus
        lev=fp.Leveys
        pit=fp.Pituus
        kul=fp.Kulma
        alaskul = fp.AlasKulma
        alaskor = fp.AlasKorkeus          
       
        edge1 = Part.makeLine((0,0,0), (pit,0,0)) #lines needed to create rectangle
        edge2 = Part.makeLine((0,0,0),(0,0,kor))
        edge3 = Part.makeLine((pit,0,0), (pit,0,alaskor))
        edge4 = Part.makeLine((0,0,kor), (pit,0,alaskor))
        takeof = Part.makeLine((-kor/tan(kul*2*pi/360),0,0),(0,0,kor))
        takeofpohja = Part.makeLine((-kor/tan(kul*2*pi/360),0,0),(0,0,0))
        takeofpysty = Part.makeLine((0,0,0),(0,0,kor))
        land = Part.makeLine((pit,0,alaskor),(pit+alaskor/tan(alaskul*pi*2/360),0,0))
        landpohja = Part.makeLine((pit,0,0),(pit+alaskor/tan(alaskul*pi*2/360),0,0))
        lentorata = lento(0,0,cos(kul*pi*2./360.)*nop/3.6,sin(kul*pi*2./360.)*nop/3.6) #calculating the flightpath by script lento.py
        landwire=Part.Wire([edge3,land,landpohja])
        faceland=Part.Face(landwire)
        extland=faceland.extrude(Base.Vector(0,lev,0)) #extrude landing
        #make for loop to catch the steps of the flightpath
        for i in range(len(lentorata[1])-1):
        	if i==0:
        		seg=Part.makeLine((lentorata[1][i,0],0,kor+lentorata[2][i,0]),(lentorata[1][i+1,0],0,kor+lentorata[2][i+1,0]))
        		wire2=Part.Wire([seg])
        		
        	else:
        		seg=Part.makeLine((lentorata[1][i,0],0,kor+lentorata[2][i,0]),(lentorata[1][i+1,0],0,kor+lentorata[2][i+1,0]))
        		wire2=Part.Wire([wire2,seg])
        		ve=wire2.Vertexes[1]
        #next thing when hit landing
        #while path_x == land_x and path_y < land_y
        #try:
        #	ve=wire2.Vertexes[i]
        #	extland.isInside(Base.Vector(ve.X,ve.Y,ve.Z)

        #edgerandom = Part.makeLine((0,0,kor), (,lev,kor))
        #roska=Part.Wire([edgerandom])
        takeofwire =Part.Wire([takeof,takeofpohja,takeofpysty])

        wire1 = Part.Wire([edge1,edge2,edge3,edge4]) #rectangle
        face1 = Part.Face(wire1) #face from rectangle
        facetakeof = Part.Face(takeofwire)
        ext=face1.extrude(Base.Vector(0,lev,0)) #extrude the (face)
        exttake = facetakeof.extrude(Base.Vector(0,lev,0)) #extrude takeof
        extflight = wire2.extrude(Base.Vector(0,lev/2,0)) #extrude flightpath

        final=Part.Compound([extflight,ext,exttake,extland])
        fp.Shape = final #ext #result shape

def makePaskaLaatikko():
    doc = FreeCAD.activeDocument()
    if doc == None:
        doc = FreeCAD.newDocument()
    paskalaatikko=doc.addObject("Part::FeaturePython","Paska_Laatikko") #add object to document
    paskalaatikko.Label = "Paska Laatikko"
    PaskaLaatikko(paskalaatikko)
    paskalaatikko.ViewObject.Proxy=0

if __name__ == "__main__": #feature will be generated after macro execution
    makePaskaLaatikko()
