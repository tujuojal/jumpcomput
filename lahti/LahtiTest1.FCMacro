from __future__ import division # allows floating point division from integers
import FreeCAD, Part, math
from FreeCAD import Base
from lento import lento
from inrun import inrun
from inrun import takeoff
from scipy import *

class LahtiTest1:
    def __init__(self, obj):
        ''' Add the properties: Korkeus, Leveys, Pituus, Segments (see Property View) '''
        obj.addProperty("App::PropertyLength","Korkeus","Laatikko","Laatikon korkeus").Korkeus=20.0
        obj.addProperty("App::PropertyLength","Leveys","Laatikko","Laatikon leveys").Leveys=30.0
        obj.addProperty("App::PropertyLength","Pituus","Laatikko","Length of the block").Pituus=20.0
        obj.addProperty("App::PropertyLength","Segments","Laatikko","Number of the line segments").Segments=72
        obj.addProperty("App::PropertyLength","Kulma","Laatikko","Nokan kulma").Kulma=30.0
        obj.addProperty("App::PropertyLength","AlasKulma","Laatikko","Alastulon kulma").AlasKulma=30.0
        obj.addProperty("App::PropertyLength","AlasKorkeus","Laatikko","Alastulon korkeus").AlasKorkeus=20.0
        obj.addProperty("App::PropertyLength","Nopeus","Laatikko","Nopeus nokalla km/h").Nopeus=40.0
        obj.addProperty("App::PropertyLength","InrunHeight","Laatikko","Inrun korkeus").InrunHeight=25.0
        obj.addProperty("App::PropertyLength","RunAngle","Laatikko","Vauhdinoton kulma").RunAngle=31.0
        obj.addProperty("App::PropertyLength","Radius","Laatikko","Transition sade").Radius=20.0
        obj.addProperty("App::PropertyLength","Flat","Laatikko","Flatin pituus").Flat=5.0
        obj.Proxy = self

    def onChanged(self, fp, prop):
        if prop == "Nopeus" or prop == "Korkeus" or prop == "Kulma" or prop == "Leveys" or prop == "Pituus" or prop == "Segments" or prop=="AlasKorkeus" or prop == "AlasKulma" or prop == "InrunHeight" or prop == "RunAngle" or prop == "Radius" or prop== "Flat" : #if one of these is changed
            self.execute(fp)

    def execute(self, fp): #main part of script
        steps=int(fp.Segments) #get value from property
        
        nop=fp.Nopeus
        kor=fp.Korkeus
        lev=fp.Leveys
        pit=fp.Pituus
        kul=fp.Kulma
        alaskul = fp.AlasKulma
        alaskor = fp.AlasKorkeus          
	ylengthstr = fp.InrunHeight
	runangle = fp.RunAngle
	radius = fp.Radius
	flat = fp.Flat
       
	inruninfo = inrun(runangle*2.*pi/360.,0,0,0,ylengthstr,runangle*2.*pi/360.,radius,flat)				#inrun path
	[kode,sxloppu,syloppu,vxloppu,vyloppu] = takeoff(ylengthstr,runangle*2.*pi/360.,radius,flat) #checkin the takeoff point
	print kode
	print vyloppu

        edge1 = Part.makeLine((sxloppu,0,syloppu), (sxloppu+pit,0,syloppu+alaskor-kor)) #lines needed to create rectangle
        edge2 = Part.makeLine((sxloppu,0,syloppu-kor),(sxloppu,0,syloppu))
        edge3 = Part.makeLine((sxloppu+pit,0,syloppu-kor), (sxloppu+pit,0,syloppu+alaskor-kor))
        edge4 = Part.makeLine((sxloppu,0,syloppu-kor), (sxloppu+pit,0,syloppu-kor))
        takeof = Part.makeLine((-kor/tan(kul*2*pi/360)+sxloppu,0,syloppu-kor),(sxloppu,0,syloppu))
        takeofpohja = Part.makeLine((-kor/tan(kul*2*pi/360)+sxloppu,0,syloppu-kor),(sxloppu,0,syloppu-kor))
        takeofpysty = Part.makeLine((sxloppu,0,syloppu-kor),(sxloppu,0,syloppu))
        land = Part.makeLine((sxloppu+pit,0,syloppu+alaskor-kor),(sxloppu+pit+alaskor/tan(alaskul*pi*2/360),0,syloppu-kor))
        landpohja = Part.makeLine((sxloppu+pit,0,syloppu-kor),(sxloppu+pit+alaskor/tan(alaskul*pi*2/360),0,syloppu-kor))
#
#
        lentorata = lento(sxloppu,syloppu,vxloppu,vyloppu) #calculating the flightpath by script lento.py
        landwire=Part.Wire([edge3,land,landpohja])
        faceland=Part.Face(landwire)
        extland=faceland.extrude(Base.Vector(0,lev,0)) #extrude landing


        #make for loop to catch the steps of the inruninfo
        for i in range(len(inruninfo[1][:kode])-1):
        	if i==0:
        		segInrun=Part.makeLine((inruninfo[1][i,0],0,inruninfo[2][i,0]),(inruninfo[1][i+1,0],0,inruninfo[2][i+1,0]))
        		wireInrun=Part.Wire([segInrun])
        		
        	else:
        		segInrun=Part.makeLine((inruninfo[1][i,0],0,inruninfo[2][i,0]),(inruninfo[1][i+1,0],0,inruninfo[2][i+1,0]))
        		wireInrun=Part.Wire([wireInrun,segInrun])
        		veInrun=wireInrun.Vertexes[1]

        extInrun = wireInrun.extrude(Base.Vector(0,lev/2,0)) #extrude inruninfo
        #make for loop to catch the steps of the flightpath
        for i in range(len(lentorata[1])-1):
        	if i==0:
        		seg=Part.makeLine((lentorata[1][i,0],0,lentorata[2][i,0]),(lentorata[1][i+1,0],0,lentorata[2][i+1,0]))
        		wire2=Part.Wire([seg])
        		
        	else:
        		seg=Part.makeLine((lentorata[1][i,0],0,lentorata[2][i,0]),(lentorata[1][i+1,0],0,lentorata[2][i+1,0]))
        		wire2=Part.Wire([wire2,seg])
        		ve=wire2.Vertexes[1]
        #next thing when hit landing
        #while path_x == land_x and path_y < land_y
        #try:
        #	ve=wire2.Vertexes[i]
        #	extland.isInside(Base.Vector(ve.X,ve.Y,ve.Z)

        #edgerandom = Part.makeLine((0,0,kor), (,lev,kor))
        #roska=Part.Wire([edgerandom])
        takeofwire =Part.Wire([takeof,takeofpohja,takeofpysty])

        wire1 = Part.Wire([edge1,edge2,edge3,edge4]) #rectangle
        face1 = Part.Face(wire1) #face from rectangle
        facetakeof = Part.Face(takeofwire)
        ext=face1.extrude(Base.Vector(0,lev,0)) #extrude the (face)
        exttake = facetakeof.extrude(Base.Vector(0,lev,0)) #extrude takeof
        extflight = wire2.extrude(Base.Vector(0,lev/2,0)) #extrude flightpath

        final=Part.Compound([extInrun,extflight,ext,exttake,extland])
        fp.Shape = final #ext #result shape

def makeLahtiTest1():
    doc = FreeCAD.activeDocument()
    if doc == None:
        doc = FreeCAD.newDocument()
    lahtiTest1=doc.addObject("Part::FeaturePython","Lahti_testing") #add object to document
    lahtiTest1.Label = "Lahti testing"
    LahtiTest1(lahtiTest1)
    lahtiTest1.ViewObject.Proxy=0

if __name__ == "__main__": #feature will be generated after macro execution
    makeLahtiTest1()
